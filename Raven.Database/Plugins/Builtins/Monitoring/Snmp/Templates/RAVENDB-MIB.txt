-- Copyright (C) 2015 Hibernating Rhinos, Ltd.  All Rights Reserved.

RAVENDB-MIB DEFINITIONS ::= BEGIN

IMPORTS
   enterprises, MODULE-IDENTITY, Integer32, TimeTicks, Gauge32
      FROM SNMPv2-SMI
   OBJECT-TYPE
      FROM RFC1155-SMI
   DisplayString
      FROM SNMPv2-TC;

ravendb MODULE-IDENTITY
    LAST-UPDATED "201505040000Z"
    ORGANIZATION "Hibernating Rhinos Ltd"
    CONTACT-INFO "http://www.hibernatingrhinos.com/about"
    DESCRIPTION "MIB for the RavenDB"
    REVISION "201505040000Z"
    DESCRIPTION "updated MIB"
    ::= { software 1 }
      
hibernatingRhinos      			OBJECT IDENTIFIER ::= { enterprises 45751 }
software        				OBJECT IDENTIFIER ::= { hibernatingRhinos 1 }

server                  		OBJECT IDENTIFIER ::= { ravendb 1 }
serverRequests                  OBJECT IDENTIFIER ::= { server 6 }
serverMemory                  	OBJECT IDENTIFIER ::= { server 8 }

resources                  		OBJECT IDENTIFIER ::= { ravendb 5 }
resourcesCounts                 OBJECT IDENTIFIER ::= { resources 1 }
databases                  		OBJECT IDENTIFIER ::= { resources 2 }

systemDatabase                  OBJECT IDENTIFIER ::= { databases 1 }
systemDatabaseStatistics		OBJECT IDENTIFIER ::= { systemDatabase 1 }
systemDatabaseStorageStatistics	OBJECT IDENTIFIER ::= { systemDatabase 2 }
systemDatabaseMetrics			OBJECT IDENTIFIER ::= { systemDatabase 3 }
systemDatabaseIndexStatistics	OBJECT IDENTIFIER ::= { systemDatabase 5 }
systemDatabaseRequests			OBJECT IDENTIFIER ::= { systemDatabaseMetrics 4 }
systemDatabaseRequestsDuration	OBJECT IDENTIFIER ::= { systemDatabaseRequests 2 }

systemDatabaseIndexes			OBJECT IDENTIFIER ::= { systemDatabase 4 }
systemDatabase1Index			OBJECT IDENTIFIER ::= { systemDatabaseIndexes 1 }

--rootOid 1.3.6.1.4.1.45751.1.1.

--1. Server
--1.1. Server name
--1.2. Server up time
--1.3. Server build version
--1.4. Server product version
--1.5. Server PID
--1.6.1. Server concurrent requests
--1.6.2. Server total requests
--1.7. Server CPU
--1.8.1 Server total memory
--1.9. Server url
--1.10 Server indexing errors (global)

--5. Resources
--5.1.1 Database total count
--5.1.2 Database loaded count

--5.2.X Database
--5.2.X.1. Database statistics
--5.2.X.1.1 Database name
--5.2.X.1.2 Database count of indexes
--5.2.X.1.3 Database stale count
--5.2.X.1.4 Database count of transformers
--5.2.X.1.5 Database approximate task count
--5.2.X.1.6 Database count of documents
--5.2.X.1.7 Database count of attachments
--5.2.X.1.8 Database CurrentNumberOfItemsToIndexInSingleBatch
--5.2.X.1.9 Database CurrentNumberOfItemsToReduceInSingleBatch
--5.2.X.1.10 Database errors (count)
--5.2.X.1.11 Database id
--5.2.X.1.12 Database active bundles
--5.2.X.1.13 Database loaded
--5.2.X.2. Database storage statistics
--5.2.X.2.1. Database transactional storage allocated size
--5.2.X.2.2. Database transactional storage used size
--5.2.X.2.3. Database index storage size
--5.2.X.3.4. Database total size
--5.2.X.2.5. Database transactional storage drive remaining space
--5.2.X.2.6. Database index storage drive remaining space
--5.2.X.3. Database metrics
--5.2.X.3.1. Database docs write per second
--5.2.X.3.2. Database indexed per second
--5.2.X.3.3. Database reduced per second
--5.2.X.3.4. Database requests
--5.2.X.3.4.1. Database requests per second
--5.2.X.3.4.2. Database requests duration
--5.2.X.3.4.2.1. Database requests duration last minute avg
--5.2.X.3.4.2.2. Database requests duration last minute max
--5.2.X.3.4.2.3. Database requests duration last minute min

--5.2.X.4. Database indexes
--5.2.X.4.Y. Index
--5.2.X.4.Y.1. Index exists
--5.2.X.4.Y.2. Index name
--5.2.X.4.Y.3. Index id
--5.2.X.4.Y.4. Index priority
--5.2.X.4.Y.5. Indexing attempts
--5.2.X.4.Y.6. Indexing successes
--5.2.X.4.Y.7. Indexing errors
--5.2.X.4.Y.8. Reduce indexing attempts
--5.2.X.4.Y.9. Reduce indexing successes
--5.2.X.4.Y.10. Reduce indexing errors
--5.2.X.4.Y.11. Time since last query
--5.2.X.5. Database index statistics
--5.2.X.5.1. Number of indexes
--5.2.X.5.2. Number of static indexes
--5.2.X.5.3. Number of auto indexes
--5.2.X.5.4. Number of idle indexes
--5.2.X.5.5. Number of abandoned indexes
--5.2.X.5.6. Number of disabled indexes
--5.2.X.5.7. Number of error indexes

--5.2.X.6. Database bundles
--5.2.X.6.1. Replication bundle
--5.2.X.6.1.1. Replication active
--5.2.X.6.1.2.Y. Replication destinations
--5.2.X.6.1.2.Y.1. Replication destination enabled
--5.2.X.6.1.2.Y.2. Replication destination url
--5.2.X.6.1.2.Y.3. Time since last replication

--------
--server
--------

serverName OBJECT-TYPE
   SYNTAX DisplayString (SIZE (0..255))
   MAX-ACCESS read-only
   STATUS current
   DESCRIPTION
      "name"
   ::= { server 1 }
   
serverUpTime OBJECT-TYPE
   SYNTAX TimeTicks
   MAX-ACCESS read-only
   STATUS current
   DESCRIPTION
      "uptime"
   ::= { server 2 }
   
serverBuildVersion OBJECT-TYPE
   SYNTAX DisplayString (SIZE (0..255))
   MAX-ACCESS read-only
   STATUS current
   DESCRIPTION
      "build version"
   ::= { server 3 }
   
serverProductVersion OBJECT-TYPE
   SYNTAX DisplayString (SIZE (0..255))
   MAX-ACCESS read-only
   STATUS current
   DESCRIPTION
      "product version"
   ::= { server 4 }
   
serverPid OBJECT-TYPE
   SYNTAX Integer32
   MAX-ACCESS read-only
   STATUS current
   DESCRIPTION
      "PID of server process"
   ::= { server 5 }
   
serverConcurrentRequests OBJECT-TYPE
   SYNTAX Integer32
   MAX-ACCESS read-only
   STATUS current
   DESCRIPTION
      "number of concurrent requests"
   ::= { serverRequests 1 }

serverTotalRequests OBJECT-TYPE
   SYNTAX Integer32
   MAX-ACCESS read-only
   STATUS current
   DESCRIPTION
      "total number of requests"
   ::= { serverRequests 2 }
   
serverCpu OBJECT-TYPE
   SYNTAX Gauge32
   MAX-ACCESS read-only
   STATUS current
   DESCRIPTION
      "CPU usage (%)"
   ::= { server 7 }
   
serverTotalMemory OBJECT-TYPE
   SYNTAX Gauge32
   MAX-ACCESS read-only
   STATUS current
   DESCRIPTION
      "total memory usage (MB)"
   ::= { serverMemory 1 }
   
serverUrl OBJECT-TYPE
   SYNTAX DisplayString (SIZE (0..255))
   MAX-ACCESS read-only
   STATUS current
   DESCRIPTION
      "url"
   ::= { server 9 }

serverIndexingErrors OBJECT-TYPE
   SYNTAX Gauge32
   MAX-ACCESS read-only
   STATUS current
   DESCRIPTION
      "# of indexing errors for all loaded databases"
   ::= { server 10 }

serverLastRequestTime OBJECT-TYPE
   SYNTAX TimeTicks
   MAX-ACCESS read-only
   STATUS current
   DESCRIPTION
      "time since last request"
   ::= { server 11 }

-----------
--resources
-----------

databaseTotalCount OBJECT-TYPE
   SYNTAX Integer32
   MAX-ACCESS read-only
   STATUS current
   DESCRIPTION
      "# of databases"
   ::= { resourcesCounts 1 }
   
databaseLoadedCount OBJECT-TYPE
   SYNTAX Integer32
   MAX-ACCESS read-only
   STATUS current
   DESCRIPTION
      "# of loaded databases"
   ::= { resourcesCounts 2 }
 
-----------
--databases
-----------

--database statistics
 
systemDatabaseName OBJECT-TYPE
   SYNTAX DisplayString (SIZE (0..255))
   MAX-ACCESS read-only
   STATUS current
   DESCRIPTION
      "database name"
   ::= { systemDatabaseStatistics 1 }
   
systemDatabaseCountOfIndexes OBJECT-TYPE
   SYNTAX Gauge32
   MAX-ACCESS read-only
   STATUS current
   DESCRIPTION
      "# of indexes in database"
   ::= { systemDatabaseStatistics 2 }
   
systemDatabaseCountOfStaleIndexes OBJECT-TYPE
   SYNTAX Gauge32
   MAX-ACCESS read-only
   STATUS current
   DESCRIPTION
      "# of stale indexes in database"
   ::= { systemDatabaseStatistics 3 }

systemDatabaseCountOfTransformers OBJECT-TYPE
   SYNTAX Gauge32
   MAX-ACCESS read-only
   STATUS current
   DESCRIPTION
      "# of transformers in database"
   ::= { systemDatabaseStatistics 4 }
   
systemDatabaseApproximateTaskCount OBJECT-TYPE
   SYNTAX Gauge32
   MAX-ACCESS read-only
   STATUS current
   DESCRIPTION
      "approximate # of tasks in database"
   ::= { systemDatabaseStatistics 5 }
   
systemDatabaseCountOfDocuments OBJECT-TYPE
   SYNTAX Gauge32
   MAX-ACCESS read-only
   STATUS current
   DESCRIPTION
      "# of documents in database"
   ::= { systemDatabaseStatistics 6 }
   
systemDatabaseCountOfAttachments OBJECT-TYPE
   SYNTAX Gauge32
   MAX-ACCESS read-only
   STATUS current
   DESCRIPTION
      "# of attachments in database"
   ::= { systemDatabaseStatistics 7 }
   
systemDatabaseNumberOfItemsToIndexInSingleBatch OBJECT-TYPE
   SYNTAX Gauge32
   MAX-ACCESS read-only
   STATUS current
   DESCRIPTION
      "# of items to index in single batch in database"
   ::= { systemDatabaseStatistics 8 }

systemDatabaseNumberOfItemsToReduceInSingleBatch OBJECT-TYPE
   SYNTAX Gauge32
   MAX-ACCESS read-only
   STATUS current
   DESCRIPTION
      "# of items to reduce in single batch in database"
   ::= { systemDatabaseStatistics 9 }

systemDatabaseCountOfErrors OBJECT-TYPE
   SYNTAX Integer32
   MAX-ACCESS read-only
   STATUS current
   DESCRIPTION
      "# of errors in database"
   ::= { systemDatabaseStatistics 10 }
   
systemDatabaseId OBJECT-TYPE
   SYNTAX DisplayString (SIZE (0..255))
   MAX-ACCESS read-only
   STATUS current
   DESCRIPTION
      "database Id"
   ::= { systemDatabaseStatistics 11 }
   
systemDatabaseActiveBundles OBJECT-TYPE
   SYNTAX DisplayString (SIZE (0..255))
   MAX-ACCESS read-only
   STATUS current
   DESCRIPTION
      "list of active bundles for database"
   ::= { systemDatabaseStatistics 12 }
   
systemDatabaseLoaded OBJECT-TYPE
   SYNTAX DisplayString (SIZE (0..255))
   MAX-ACCESS read-only
   STATUS current
   DESCRIPTION
      "indicates if database is loaded or not"
   ::= { systemDatabaseStatistics 13 }

--database storage statistics

systemDatabaseTransactionalStorageAllocatedSize OBJECT-TYPE
   SYNTAX Gauge32
   MAX-ACCESS read-only
   STATUS current
   DESCRIPTION
      "# of allocated MB used by transactional storage"
   ::= { systemDatabaseStorageStatistics 1 }

systemDatabaseTransactionalStorageUsedSize OBJECT-TYPE
   SYNTAX Gauge32
   MAX-ACCESS read-only
   STATUS current
   DESCRIPTION
      "# of MB used by transactional storage"
   ::= { systemDatabaseStorageStatistics 2 }

systemDatabaseIndexStorageSize OBJECT-TYPE
   SYNTAX Gauge32
   MAX-ACCESS read-only
   STATUS current
   DESCRIPTION
      "# of MB used by index storage"
   ::= { systemDatabaseStorageStatistics 3 }
   
systemDatabaseTotalSize OBJECT-TYPE
   SYNTAX Gauge32
   MAX-ACCESS read-only
   STATUS current
   DESCRIPTION
      "total # of MB used by database"
   ::= { systemDatabaseStorageStatistics 4 }

systemDatabaseTransactionalStorageDiskRemainingSpace OBJECT-TYPE
   SYNTAX Gauge32
   MAX-ACCESS read-only
   STATUS current
   DESCRIPTION
      "# of MB left on disk used by transactional storage"
   ::= { systemDatabaseStorageStatistics 5 }

systemDatabaseIndexStorageDiskRemainingSpace OBJECT-TYPE
   SYNTAX Gauge32
   MAX-ACCESS read-only
   STATUS current
   DESCRIPTION
      "# of MB left on disk used by index storage"
   ::= { systemDatabaseStorageStatistics 6 }

--database metrics

systemDatabaseDocsWritePerSecond OBJECT-TYPE
   SYNTAX Gauge32
   MAX-ACCESS read-only
   STATUS current
   DESCRIPTION
      "# of documents written per second"
   ::= { systemDatabaseMetrics 1 }

systemDatabaseIndexedPerSecond OBJECT-TYPE
   SYNTAX Gauge32
   MAX-ACCESS read-only
   STATUS current
   DESCRIPTION
      "# of documents indexed per second"
   ::= { systemDatabaseMetrics 2 }

systemDatabaseReducedPerSecond OBJECT-TYPE
   SYNTAX Gauge32
   MAX-ACCESS read-only
   STATUS current
   DESCRIPTION
      "# of reductions per second"
   ::= { systemDatabaseMetrics 3 }

systemDatabaseRequestsPerSecond OBJECT-TYPE
   SYNTAX Gauge32
   MAX-ACCESS read-only
   STATUS current
   DESCRIPTION
      "# of requests per second"
   ::= { systemDatabaseRequests 1 }

systemDatabaseRequestsDurationLastMinuteAvg OBJECT-TYPE
   SYNTAX Gauge32
   MAX-ACCESS read-only
   STATUS current
   DESCRIPTION
      "requests duration mean"
   ::= { systemDatabaseRequestsDuration 1 }

systemDatabaseRequestsDurationLastMinuteMin OBJECT-TYPE
   SYNTAX Gauge32
   MAX-ACCESS read-only
   STATUS current
   DESCRIPTION
      "requests duration min"
   ::= { systemDatabaseRequestsDuration 2 }
   
systemDatabaseRequestsDurationLastMinuteMax OBJECT-TYPE
   SYNTAX Gauge32
   MAX-ACCESS read-only
   STATUS current
   DESCRIPTION
      "requests duration max"
   ::= { systemDatabaseRequestsDuration 3 }

--database index statistics

systemDatabaseNumberOfIndexes OBJECT-TYPE
   SYNTAX Integer32
   MAX-ACCESS read-only
   STATUS current
   DESCRIPTION
      "# of indexes in database"
   ::= { systemDatabaseIndexStatistics 1 }

systemDatabaseNumberOfStaticIndexes OBJECT-TYPE
   SYNTAX Integer32
   MAX-ACCESS read-only
   STATUS current
   DESCRIPTION
      "# of static indexes in database"
   ::= { systemDatabaseIndexStatistics 2 }

systemDatabaseNumberOfAutoIndexes OBJECT-TYPE
   SYNTAX Integer32
   MAX-ACCESS read-only
   STATUS current
   DESCRIPTION
      "# of auto indexes in database"
   ::= { systemDatabaseIndexStatistics 3 }

systemDatabaseNumberOfIdleIndexes OBJECT-TYPE
   SYNTAX Integer32
   MAX-ACCESS read-only
   STATUS current
   DESCRIPTION
      "# of idle indexes in database"
   ::= { systemDatabaseIndexStatistics 4 }

systemDatabaseNumberOfAbandonedIndexes OBJECT-TYPE
   SYNTAX Integer32
   MAX-ACCESS read-only
   STATUS current
   DESCRIPTION
      "# of abandoned indexes in database"
   ::= { systemDatabaseIndexStatistics 5 }

systemDatabaseNumberOfDisabledIndexes OBJECT-TYPE
   SYNTAX Integer32
   MAX-ACCESS read-only
   STATUS current
   DESCRIPTION
      "# of disabled indexes in database"
   ::= { systemDatabaseIndexStatistics 6 }

systemDatabaseNumberOfErrorIndexes OBJECT-TYPE
   SYNTAX Integer32
   MAX-ACCESS read-only
   STATUS current
   DESCRIPTION
      "# of idle indexes in database"
   ::= { systemDatabaseIndexStatistics 7 }

--database indexes

systemDatabase1IndexExists OBJECT-TYPE
   SYNTAX DisplayString (SIZE (0..255))
   MAX-ACCESS read-only
   STATUS current
   DESCRIPTION
      "indicates if index exists"
   ::= { systemDatabase1Index 1 }

systemDatabase1IndexName OBJECT-TYPE
   SYNTAX DisplayString (SIZE (0..255))
   MAX-ACCESS read-only
   STATUS current
   DESCRIPTION
      "index name"
   ::= { systemDatabase1Index 2 }

systemDatabase1IndexId OBJECT-TYPE
   SYNTAX Integer32
   MAX-ACCESS read-only
   STATUS current
   DESCRIPTION
      "index Id"
   ::= { systemDatabase1Index 3 }

systemDatabase1IndexPriority OBJECT-TYPE
   SYNTAX DisplayString (SIZE (0..255))
   MAX-ACCESS read-only
   STATUS current
   DESCRIPTION
      "index priority"
   ::= { systemDatabase1Index 4 }

systemDatabase1IndexAttempts OBJECT-TYPE
   SYNTAX Integer32
   MAX-ACCESS read-only
   STATUS current
   DESCRIPTION
      "# of indexing attempts"
   ::= { systemDatabase1Index 5 }

systemDatabase1IndexSuccesses OBJECT-TYPE
   SYNTAX Integer32
   MAX-ACCESS read-only
   STATUS current
   DESCRIPTION
      "# of indexing successes"
   ::= { systemDatabase1Index 6 }

systemDatabase1IndexErrors OBJECT-TYPE
   SYNTAX Integer32
   MAX-ACCESS read-only
   STATUS current
   DESCRIPTION
      "# of indexing errors"
   ::= { systemDatabase1Index 7 }

systemDatabase1IndexReduceAttempts OBJECT-TYPE
   SYNTAX Integer32
   MAX-ACCESS read-only
   STATUS current
   DESCRIPTION
      "# of reduce attempts"
   ::= { systemDatabase1Index 8 }

systemDatabase1IndexReduceSuccesses OBJECT-TYPE
   SYNTAX Integer32
   MAX-ACCESS read-only
   STATUS current
   DESCRIPTION
      "# of reduce successes"
   ::= { systemDatabase1Index 9 }

systemDatabase1IndexReduceErrors OBJECT-TYPE
   SYNTAX Integer32
   MAX-ACCESS read-only
   STATUS current
   DESCRIPTION
      "# of reduce errors"
   ::= { systemDatabase1Index 10 }

systemDatabase1IndexTimeSinceLastQuery OBJECT-TYPE
   SYNTAX TimeTicks
   MAX-ACCESS read-only
   STATUS current
   DESCRIPTION
      "time since last query"
   ::= { systemDatabase1Index 11 }
   
END
